Messages DEFINITIONS ::= BEGIN

	
	GTXOperation ::= SEQUENCE {
		opName UTF8String,
		args SEQUENCE OF Gtv
	}
	
	GTXTransaction ::= SEQUENCE {
		blockchainRID OCTET STRING,
		operations SEQUENCE OF GTXOperation,
		signers SEQUENCE OF OCTET STRING,
		signatures SEQUENCE OF OCTET STRING
	}
	
END
